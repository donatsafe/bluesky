FME workspace AuctionBidReceiver.fmw

Parameters:
- DestDataset_SQLITE3 = $(FME_SHAREDRESOURCE_DATA)/SilentAuction2018/AuctionItems.sqlite   # SQLite Database
- AuctionItemsSQL = $(FME_SHAREDRESOURCE_DATA)/SilentAuction2018/AuctionItems.sqlite

Readers:
- TEXTLINE_1: TEXTLINE from $(FME_TOPIC_MESSAGE)

Writers:
- SQLITE3_1: SQLITE3 to $(DestDataset_SQLITE3)
- GOOGLESHEETS_1: GOOGLESHEETS to <Unused>

text_line (reader TEXTLINE_1)
    attributes: text_line_data buffer
    -> JSONFlattener
JSONFlattener
    ERROR_LIST_ATTR = _json_error
    FILEPATH_OR_URL = $(FME_TOPIC_MESSAGE)
    NEW_ATTRIBUTES = subscriber_content
    READ_FROM_FILE = YES
    RECURSIVE = Yes
    -> JSONFlattener_2
JSONFlattener_2
    ERROR_LIST_ATTR = _json_error
    JSON_DOCUMENT = @Value(subscriber_content)
    NEW_ATTRIBUTES = formValues{}
    READ_FROM_FILE = NO
    RECURSIVE = Yes
    -> AttributeManager
    <REJECTED> -> AttributeManager
AttributeManager
    ATTR_TABLE:
      SET_TO form_Timestamp = @Value(formValues{0})
      SET_TO form_EmailAddress = @Value(formValues{1})
      SET_TO form_LotNo = @Value(formValues{2})
      SET_TO form_Bid = @Value(formValues{3})
      SET_TO form_Name = @Value(form_EmailAddress)
    -> StringReplacer
StringReplacer
    CASE = NO
    FIND_TEXT = $
    NO_MATCH = _FME_NO_OP_
    REGEXP = NO
    SRC_ATTRS = form_Bid
    -> FeatureReader [INITIATOR]
Note: Will people submit with a $ or not? Logic for that
FeatureReader
    ATTRIBUTES = LotDetails,"Item,""Lot #"",Brand,Location,Comments,Price,Buyer,HighestBidder,HighestBid,HighestBidderEmail"
    ATTR_ACCUM_MODE = Merge Initiator and Result
    ATTR_CONFLICT_RES = Use Result
    COMBINE_GEOM = Use Result
    DATASET = $(AuctionItemsSQL)
    FEATURETYPES = LotDetails
    FORMAT = SQLITE3
    OUTPUT_FEATURES_DISPLAY = Schema and Data Features
    SELECTED_PORTS = LotDetails
    SQLITE3_QUERY_FEATURE_TYPES_FOR_MERGE_FILTERS = Yes
    SQLITE3_SUPPORT_INTERNATIONALIZATION = YES
    WHERE = "Lot #" = '@Value(form_LotNo)'
    LotDetails -> StringReplacer_3
StringReplacer_3
    CASE = NO
    FIND_TEXT = .|@safe.com
    NO_MATCH = _FME_NO_OP_
    REGEXP = YES
    REPLACE_TEXT = " "
    SRC_ATTRS = form_Name
    -> TestFilter
TestFilter
    DEFAULT_VALUE = UnsuccessfulBid
    TEST_LIST:
      "BOOL_OP,OR,COMPOSITE_TEST,""""""<Unused>"""""",TEST_CLAUSE,TEST HighestBid NOT_ATTRIBUTE_HAS_A_VALUE ""
      TEST @Value(form_Bid) > @Value(HighestBid)",SuccessfulBid
    SuccessfulBid -> FMEServerEmailGenerator_2
    SuccessfulBid -> FMEServerEmailGenerator_3
    SuccessfulBid -> LotDetails (writer SQLITE3_1)
    SuccessfulBid -> SlackConnector
    SuccessfulBid -> LotDetails (writer GOOGLESHEETS_1)
    UnsuccessfulBid -> FMEServerEmailGenerator
    UnsuccessfulBid -> SlackConnector_2
LotDetails (writer SQLITE3_1)
    attributes: Item text, Lot # integer, Brand text, Location text, Comments text, Price float, Buyer text, HighestBidder text, HighestBid float, HighestBidderEmail text
FMEServerEmailGenerator_2
    email_from = silentauction@safe.com
    email_replyto = silentauction@safe.com
    email_subject = Blowout Auction
    email_subscriber_content:
      Hello @TitleCase(@Value(form_Name))

      Congratulations!

      You are the highest bidder for @Value(Item) (Lot no: @Value(Lot #)).
      Your bid is $@Value(form_Bid).
    email_to = @Value(form_EmailAddress)
    -> FMEServerNotifier
LotDetails (writer GOOGLESHEETS_1)
    attributes: Item text, Lot # text, HighestBid text, Brand text, Location text, Comments text, Buyer text
FMEServerEmailGenerator_3
    email_from = silentauction@safe.com
    email_replyto = silentauction@safe.com
    email_subject = Blowout Auction
    email_subscriber_content:
      Sorry, you're no longer the highest bidder for @Value(Item)
      (Lot no: @Value(Lot #))

      The new highest bid is $@Value(form_Bid)
    email_to = @Value(HighestBidderEmail)
    -> FMEServerNotifier
FMEServerEmailGenerator
    email_from = silentauction@safe.com
    email_replyto = silentauction@safe.com
    email_subject = Blowout Auction
    email_subscriber_content = Sorry, you're not the highest bidder. The highest bid for @Value(Item) (Lot no: @Value(Lot #)) is $@Value(HighestBid)
    email_to = @Value(form_EmailAddress)
    -> FMEServerNotifier
FMEServerNotifier
    BODY = @Value(text_line_data)
    SERVER_CONNECTION = Bluesky
    TOPIC = AuctionSendEmail
SlackConnector
    BOTICON = gavel
    BOTNAME = Auctioneer
    CHANNEL = #auction_pulse
    CONNECTION = jlutherthomas_slack
    MESSAGE = New high bid of $@Value(form_Bid) for @Value(Item) (Lot no: @Value(Lot #))
    POSTTYPE = Message
    USER_OR_BOT = Bot
SlackConnector_2
    BOTICON = gavel
    BOTNAME = Auctioneer
    CHANNEL = #auction_pulse
    CONNECTION = jlutherthomas_slack
    MESSAGE = Unsuccessful bid for @Value(Item) (Lot no: @Value(Lot #)) - Current highest bid is $@Value(HighestBid)
    POSTTYPE = Message
    USER_OR_BOT = Bot

FME custom transformer FMEServerEmailGenerator
This transformer provides an easy method for creating an email message to be sent by the FME Server Notification Service.
Input Ports
Input
This transformer will accept any feature.
Output Ports
Output
Features are output with text_line_data attribute required for the Text File Writer (see Usage Notes).
text_line_data: Contains JSON-formatted message that is required by the Email Subscription (see Usage Notes).
<Rejected>
Features will be rejected if the 'To:' field does not contain a valid email address in the form email@domain. Rejected features are output with value INVALID_PARAMETER stored in the fme_rejection_code attribute.
Parameters
To
Email address for To: field. 
Cc
Email address for Cc: field.
Bcc
Email address for Bcc: field.
From
Email address for From: field.
Reply to
Email address for Reply to: field.
Subject
Text string for subject of email.
Content
The main body of the email message.
Attachments
List of files to attach to email. For multiple files, separate filenames with a comma (e.g. file1.txt,file2.txt). File paths and features stored as attributes are both accepted.
Note: Attachments may not process if not accessible by FME Server.  
Usage Notes
Step 1. Create Topic and Email Subscription
In the FME Server Web UI, create a Topic for notifications to be sent to, and also create an Email Subscription that subscribes to this Topic.
Step 2. Create a Workspace
Once you fill out the the required paramerts for this transformer, you can send the email message in two different ways:
A. Send an email when the workspace completes:
- add a Text File Writer to the workspace
- connect FMEServerEmailGenerator Output to the Text File Writer
- publish the workspace
- register it with the Job Submitter, and/or Data Download, and/or Notification Service
- for each service, click the edit button
- expand the Notify on Job Completion section
- for Topics to Publish (Success), select the Topic created in Step 1
- for the Post Data parameter, select the Text File Writer added to the workspace
- finish publishing the workspace
- now the workspace will send an email whenever it is run through the FME Server Service you registered it with  
B. Send an email using a transformer:
- add an FMEServerNotifier transformer to your workflow
- configure it to publish to the Topic that you created earlier
- for Content, select the text_line_data attribute
- now the workspace will send an email whenever it is run

Parameters:
- email_to =   # To
- email_cc =   # Cc
- email_bcc =   # Bcc
- email_from =   # From
- email_replyto =   # Reply to
- email_subject =   # Subject
- email_subscriber_content =   # Content
- email_attachment_paths =   # Attachments

Input (input)
    -> Counter
Tester_2_FAILED: Junction
    -> AttributeCreator_3
Note: Rejected
AttributeCreator_3: Junction
    -> AttributeCreator_2
AttributeCreator_2
    ATTR_TABLE = SET_TO fme_rejection_code = INVALID_PARAMETER
    -> <Rejected> (output)
<Rejected> (output)
JSONTemplater_2_ROOT: Junction
    -> JSONTemplater_2 [ROOT]
Note: No attachment
Output_2: Junction
    -> AttributeKeeper
AttributeKeeper
    KEEP_ATTRS = text_line_data
    -> Output (output)
Output (output)

Bookmark: Parse for attachement
Counter
    CNT_ATTR = _email_feature_id
    DOMAIN = counter
    SCOPE = Local
    START = 0
    -> ParameterFetcher
ParameterFetcher
    ATTR_LIST = _email_from $(email_from) _email_replyto $(email_replyto) _email_attachment_paths $(email_attachment_paths) _email_cc $(email_cc) _email_bcc $(email_bcc)
    -> AttributeCreator
AttributeCreator
    ATTR_TABLE:
      SET_TO _email_to = $(email_to)
      SET_TO _email_subject = $(email_subject)
      SET_TO _email_subscriber_content = $(email_subscriber_content)
    -> Tester_2
Note: Test that To field contains / valid email address
Note: Reject
Tester_2
    BOOL_OP = OR
    TEST_CLAUSE = TEST @Value(_email_to) CONTAINS @
    PASSED -> Tester_3
    FAILED -> Tester_2_FAILED

Bookmark: Multiple attachment string wizardy
Tester_3
    BOOL_OP = OR
    TEST_CLAUSE = TEST @Value(_email_attachment_paths) CONTAINS " "
    PASSED -> SubstringExtractor
    FAILED -> Tester_3_FAILED
SubstringExtractor
    END = -2
    RESULT_ATTR = _email_attachment_paths
    SRC_STRING = @Value(_email_attachment_paths)
    START = 1
    -> StringReplacer_3
StringReplacer_3
    CASE = NO
    FIND_TEXT = " "
    NO_MATCH = _FME_NO_OP_
    REGEXP = NO
    REPLACE_TEXT = "" ""
    SRC_ATTRS = _email_attachment_paths
    -> JSONTemplater [ROOT]
Note: Single attachment
Tester_3_FAILED: Junction
    -> JSONTemplater_2_ROOT

Bookmark: Add multiple attachments
JSONTemplater
    RESULT_ATTRIBUTE = text_line_data
    ROOT_QUERY_EXPR:
      {
      "email_to": fme:get-attribute("_email_to"),
      "email_cc": fme:get-attribute("_email_cc"),
      "email_bcc": fme:get-attribute("_email_bcc"),
      "email_from": fme:get-attribute("_email_from"),
      "email_replyto": fme:get-attribute("_email_replyto"),
      "email_subject": string(fme:get-attribute("_email_subject")),
      "subscriber_content": string(fme:get-attribute("_email_subscriber_content"))
      }
    VISIBLE_QUERY_VALIDATE = Yes
    -> Tester
Tester
    BOOL_OP = OR
    TEST_CLAUSE = TEST _email_attachment_paths ATTRIBUTE_IS_EMPTY <Unused>
    PASSED -> Tester_PASSED
    FAILED -> AttributeSplitter_2
AttributeSplitter_2
    ATTR_NAME = _email_attachment_paths
    DELIMITER = " "
    DROP_EMPTY_PARTS = No
    LIST_NAME = _email_attachment_path_list
    TRIM_OPTION = Both
    -> ListExploder_2
ListExploder_2
    ATTR_ACCUM_MODE = Merge List Attributes
    ATTR_CONFLICT_RES = Use List Attribute Values
    INDEX_ATTR = _element_index
    LIST_ATTR = _email_attachment_path_list{}
    ELEMENTS -> StringConcatenator_2
StringConcatenator_2
    ACTION = Create New Attribute
    PARM_LINE = "email_attachment{@Value(_element_index)}":@Value(_email_attachment_path_list)
    VAL_ATTR = _email_attachment_json
    -> Aggregator_2
Aggregator_2
    ACCUM_ATTRS_NAME = Merge Incoming Attributes
    AGGREGATE_TYPE = Homogeneous Collection (If Possible)
    CONCAT_ATTRS = _email_attachment_json
    GROUP_BY = _email_feature_id
    MODE = Geometry - Assemble One Level
    ORDERED = No
    SEP = ,
    AGGREGATE -> StringReplacer_5
StringReplacer_5
    CASE = NO
    FIND_TEXT = \
    NO_MATCH = _FME_NO_OP_
    REGEXP = NO
    REPLACE_TEXT = \\
    SRC_ATTRS = _email_attachment_json
    -> StringReplacer_4
StringReplacer_4
    CASE = NO
    FIND_TEXT = }
    NO_MATCH = _FME_NO_OP_
    REGEXP = NO
    REPLACE_TEXT = , @Value(_email_attachment_json)}
    SRC_ATTRS = text_line_data
    -> AttributeKeeper
Note: No attachment
Tester_PASSED: Junction
    -> Output_2

Bookmark: Add single attachment
JSONTemplater_2
    RESULT_ATTRIBUTE = text_line_data
    ROOT_QUERY_EXPR:
      {
      "email_to": fme:get-attribute("_email_to"),
      "email_cc": fme:get-attribute("_email_cc"),
      "email_bcc": fme:get-attribute("_email_bcc"),
      "email_from": fme:get-attribute("_email_from"),
      "email_replyto": fme:get-attribute("_email_replyto"),
      "email_subject": string(fme:get-attribute("_email_subject")),
      "subscriber_content": string(fme:get-attribute("_email_subscriber_content"))
      }
    VISIBLE_QUERY_VALIDATE = Yes
    -> Tester_4
Tester_4
    BOOL_OP = OR
    TEST_CLAUSE = TEST _email_attachment_paths ATTRIBUTE_IS_EMPTY <Unused>
    PASSED -> Tester_PASSED_2
    FAILED -> AttributeSplitter
AttributeSplitter
    ATTR_NAME = _email_attachment_paths
    DELIMITER = " "
    DROP_EMPTY_PARTS = No
    LIST_NAME = _email_attachment_path_list
    TRIM_OPTION = Both
    -> ListExploder
ListExploder
    ATTR_ACCUM_MODE = Merge List Attributes
    ATTR_CONFLICT_RES = Use List Attribute Values
    INDEX_ATTR = _element_index
    LIST_ATTR = _email_attachment_path_list{}
    ELEMENTS -> StringConcatenator
StringConcatenator
    ACTION = Create New Attribute
    PARM_LINE = "email_attachment{@Value(_element_index)}":"@Value(_email_attachment_path_list)"
    VAL_ATTR = _email_attachment_json
    -> Aggregator
Aggregator
    ACCUM_ATTRS_NAME = Merge Incoming Attributes
    AGGREGATE_TYPE = Homogeneous Collection (If Possible)
    CONCAT_ATTRS = _email_attachment_json
    GROUP_BY = _email_feature_id
    MODE = Geometry - Assemble One Level
    ORDERED = No
    SEP = ,
    AGGREGATE -> StringReplacer_2
StringReplacer_2
    CASE = NO
    FIND_TEXT = \
    NO_MATCH = _FME_NO_OP_
    REGEXP = NO
    REPLACE_TEXT = \\
    SRC_ATTRS = _email_attachment_json
    -> StringReplacer
StringReplacer
    CASE = NO
    FIND_TEXT = }
    NO_MATCH = _FME_NO_OP_
    REGEXP = NO
    REPLACE_TEXT = , @Value(_email_attachment_json)}
    SRC_ATTRS = text_line_data
    -> AttributeKeeper
Note: No attachment
Tester_PASSED_2: Junction
    -> Output_2
